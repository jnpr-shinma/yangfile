module device-information {
    yang-version 1;
    namespace "http://juniper.net/ns/space/device/information/1.0";
    prefix dev-info;
    organization "Juniper Networks";
    description "Example YANG module for device info";
    revision "2014-11-22" {
        description "Initial version";
    }

    grouping system {
        description "Device system info";
        leaf hostname { type string; description "Name"; }
        leaf ip { type string; description "Device mgt IP"; }
        leaf vendor { type string; description "Vendor"; }
        leaf platform { type string; description "Platform"; }
        leaf family { type string; description "Device family"; }
        leaf osVersion { type string; description "OS version"; }
        leaf serial { type string; description "Serial Number"; }
        leaf lastRebootTime { type uint32; description "Last reboot timestamp"; }
    } // container system

    grouping redundancy {
        description "Redundancy info";
        leaf masterRE { type string; description "Master RE name"; }
        leaf status { type string; description "Redundancy Status"; }
        list peer {
            description "Redundancy Peers";
            key id;
            leaf id { type uint32; description "Peer device Id"; }
            leaf name { type string; description "Peer device name"; }
        } // list peers
    } // container redundancy

    grouping configInfo {
        description "Configuration info";
        leaf schemaVersion { type string; description "Schema version"; }
        leaf configStatus { type string; description "Config Status"; }
        leaf candidateConfigState { type string; description "Candidate Config State"; }
    } // container configInfo

    grouping mgtConnection {
        description "Device connection info";
        leaf connType { type string; description "Device connection type"; }
        leaf auth { type string; description "Authentication status"; }
        leaf status { type string; description "Device connection status"; }
        leaf webMgt { type string; description "Device WebUI enabled"; }
    } // container mgtConnection
}
