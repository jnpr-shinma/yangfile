/* agwGaBillingConfig.yang generated from agwGaBillingConfig.xml */
submodule agwGaBillingConfig{

belongs-to hcta-epc {
    prefix epc;
}

import tailf-common {
    prefix tailf;
}

include mmeSgsnConfig;

include fgwConfig;

include cmdCommonHcta;            
import ietf-inet-types {
    prefix inet;
}

augment "/mme-sgsn/interface" {
    container ga {
        tailf:info "SGSN accounting interface to CGF";
        presence "";
        container agw-ga-if {
            tailf:alt-name "ga-if";
            presence ""; 
            tailf:info "Ga Interface.";
            uses routing-instance-name;
            leaf ip-address {
                tailf:info "Local IP address.";
                type inet:ip-address;
                mandatory true;
            }
            leaf echo-request-interval {
                tailf:info "Specifies time interval. Default: 1";
                type uint8 {
                    range "1..60";
                }
                default 1;
            }
            leaf drt-response-timer {
                tailf:info "DRT response timer. Default: 5";
                type uint8 {
                    range "1..30";
                }
                default 5;
            }
            leaf drt-retry {
                tailf:info "Number of DRT retries. Default: 1";
                type uint8 {
                    range "1..3";
                }
                default 1;
            }
        } /* agw-ga-if */
        list agw-cgf {
            tailf:alt-name "cgf";
            key "ip-address"; 
            max-elements 2;
            tailf:info "Charging Gateway Function.";
            leaf ip-address {
                tailf:info "CGF IP address.";
                type inet:ip-address;
                mandatory true;
            }
            leaf port {
                tailf:info "CGF Port number.";
                type uint16 {
                    range "1..65535";
                }
                mandatory true;
            }
            leaf configured-role {
                must "(count(/mme-sgsn/interface/ga/agw-cgf[configured-role = 'primary']) != 0)" {
                    error-message
                    "There must be at least one entry with the 'configured-role' field set to 'primary'";
                }
                
                must "(count(/mme-sgsn/interface/ga/agw-cgf[configured-role = 'primary']) <= 1)" {
                    error-message
                    "There can be only one 'configured-role' field set to 'primary'";
                }
                tailf:info "Specifies the role of the CGF.";
                type enumeration {
                    enum "primary" {tailf:code-name agw-cgf-configured-role-primary;}
                    enum "secondary" {tailf:code-name agw-cgf-configured-role-secondary;}
                }
                mandatory true;
            }
        } /* agw-cgf */
        container agw-sgsn-ga-profile {
            tailf:alt-name "sgsn-ga-profile";
            presence "";
            tailf:validate sgsnGaProfileValidate;
            tailf:info "SGSN Ga Profile.";
            leaf cdr-capture {
                type string {
                    pattern '(sgsn|mobility|smo|smt|sgsn,mobility|sgsn,smo|sgsn,smt|sgsn,mobility,smo|sgsn,mobility,smt|sgsn,mobility,smo,smt|mobility,smo|mobility,smt|mobility,smo,smt|smo,smt)'{
                        tailf:info "Valid values are any one of: 'sgsn,mobility,smo,smt', or a combination of these values in order.";
                    }
                }               
                tailf:info "Type of CDRs being  generated. Valid values are any one of: 'sgsn,mobility,smo,smt', or a combination of these values in order.";
                mandatory true;
            }
            leaf collection-time {
                type string {
                    pattern '(none|(((2[0-3]|[01][0-9])[:][0-5][0-9])([,](2[0-3]|[01][0-9])[:][0-5][0-9]){1,5}))' {
                        tailf:info "Valid values are: 'none' or comma separated entries in hh:mm format with a minimum of 2 and a maximum of 6 entries";
                    }
                }               
                tailf:info "Specifies the scheduled time of collection. Entries should be in hh:mm comma separated format, with a minimum of 2 and a maximum of 6 entries. Any 2 entries must be at least 4 hours apart. 'none' should be used for disabling this function. Default: none";
                default "none";
            }
            leaf encoding-scheme {
                tailf:info "Encoding scheme to CGF. Default: ber";
                type enumeration {
                    enum "per" {tailf:code-name agw-sgsn-ga-profile-encoding-scheme-per;}
                    enum "ber" {tailf:code-name agw-sgsn-ga-profile-encoding-scheme-ber;}
                }
                default "ber";
            }
            leaf version {
                tailf:info "3GPP specs applicable to this interface are TS32.015 and TS32.298. Default: 10.12.0";
                type enumeration {
                    enum "9.6.1" {tailf:code-name sgsn-ga-profile-version_9_6_1;}
                    enum "10.12.0" {tailf:code-name sgsn-ga-profile-version_10_12_0;}
                }
                default "10.12.0";
            }
            leaf partial-cdr-type {
                tailf:info "Type of partial CDR generated. Default: full";
                type enumeration {
                    enum "full" {tailf:code-name agw-sgsn-ga-profile-partial-cdr-type-full;}
                    enum "reduced" {tailf:code-name agw-sgsn-ga-profile-partial-cdr-type-reduced;}
                }
                default "full";
            }
            leaf roamer-capture {
                tailf:info "Whether CDRs should be generated for all subscribers or only roamers. Default: all";
                type enumeration {
                    enum "all" {tailf:code-name agw-sgsn-ga-profile-roamer-capture-all;}
                    enum "roamer" {tailf:code-name agw-sgsn-ga-profile-roamer-capture-roamer;}
                }
                default "all";
            }
            leaf tariff-time-change-trigger {
                tailf:info "Specifies whether the Tariff Time Change Trigger(TTCT) feature is enabled or disabled. Default: disable";
                type enumeration {
                    enum "disable" {tailf:code-name agw-sgsn-ga-profile-tariff-time-change-trigger-disable;}
                    enum "enable" {tailf:code-name agw-sgsn-ga-profile-tariff-time-change-trigger-enable;}
                }
                default "disable";
            }
        } /* agw-sgsn-ga-profile */
        container agw-charging-characteristics {
            tailf:alt-name "charging-characteristics";
            presence "";
            tailf:info "Charging Characteristics.";
            leaf scdr-partial-record-interval {
                tailf:info "Maximum amount of time an S-CDR is open before a partial record is generated. Default: 0";
                type uint16{
                    range "0|15..1440";
                }
                default 0;
            }
            leaf data-volume-limit {
                tailf:info "Combined uplink and downlink kilobytes. Default: 128";
                type uint32 {
                tailf:info "Valid values are between 128KB to 2GB";
                    range "128..2097152";
                }
                default 128;
            }
            leaf scdr-max-containers {
                tailf:info "Maximum number of 'list of traffic data volumes' containers allowed. Default: 5";
                type uint8 {
                    range "1..10";
                }
                default 5;
            }
            leaf mcdr-partial-record-interval {
                tailf:info "Time interval for M-CDR generation. Default: 0";
                type uint16{
                    range "0|15..1440";
                }
                default 0;
            }
            leaf mcdr-max-containers {
                tailf:info "Maximum number of Change of Location containers. Default: 5";
                type uint8 {
                    range "1..10";
                }
                default 5;
            }
            leaf location-based-billing {
                tailf:info "Location based billing. Default: disable";
                type enumeration {
                    enum "disable" {tailf:code-name agw-charging-characteristics-location-based-billing-disable;}
                    enum "enable" {tailf:code-name agw-charging-characteristics-location-based-billing-enable;}
                }
                default "disable";
            }
        } /* agw-charging-characteristics */
    } /* ga */
} /* interface */
} /*submodule*/
