/* agwCmnDnsConfig.yang generated from agwCmnDnsConfig.xml */
submodule agwCmnDnsConfig{

belongs-to hcta-epc {
    prefix epc;
}

import tailf-common {
    prefix tailf;
}

include mmeSgsnConfig;

include fgwConfig;

include cmdCommonHcta;
import ietf-inet-types {
    prefix inet;
}

augment "/mme-sgsn" {
    container dns {
        tailf:info "DNS objects";
        presence ""; 
        list agw-dns-server {
            tailf:alt-name "server";
            tailf:validate dnsServerValidate {
                tailf:call-once "true";
            }
            key "server-name";
            max-elements 8; 	     
            tailf:info "AGW CMN DNS Server";
            leaf server-name {
                tailf:info "The name for this DNS Server";
                type string {
                    length "1..254";
                }
                mandatory true;
            }
            leaf server-ip-address {
                tailf:info "The IP Address for this DNS Server";
                type inet:ip-address;
                mandatory true;
            }
            leaf weight {
                tailf:info "The weight for this DNS Server Default 10";
                type uint16 {
                    range "1..10";
                }
                default 10;
            }
        } /* agw-dns-server */
        container  static-cache {
            tailf:info "Static-cache objects";
            tailf:validate dnsStaticCacheValidate;
            presence ""; 
            list agw-dns-static-a {
                tailf:alt-name "a-record";
                key "entry-index"; 
                max-elements 1000; 	     
                tailf:info "DNS Static Cache 'A' Record database table.";
                leaf entry-index {
                    tailf:info "The index which uniquely identifies this record";
                    type uint16 {
                        range "1..65535";
                    }
                    mandatory true;
                }
                leaf node-name {
                    tailf:info "A unique identifier for the node referenced with this DNS entry.";
                    type string {
                        length "1..254";
                    }
                    mandatory true;
                }
                leaf node-ip-address {
                    tailf:info "IP address of the node.";
                    type inet:ipv4-address;
                    mandatory true;
                }
            } /* agw-dns-static-a */
            list agw-dns-static-aaaa {
                tailf:alt-name "aaaa-record";
                key "entry-index"; 
                max-elements 1000; 	     
                tailf:info "DNS Static Cache 'AAAA' Record database table.";
                leaf entry-index {
                    tailf:info "The index which uniquely identifies this record";
                    type uint16 {
                        range "1..65535";
                    }
                    mandatory true;
                }
                leaf node-name {
                    tailf:info "A unique identifier for the node referenced with this DNS entry.";
                    type string {
                        length "1..254";
                    }
                    mandatory true;
                }
                leaf node-ip-address {
                    tailf:info "IP address of the node.";
                    type inet:ipv6-address;
                    mandatory true;
                }
            } /* agw-dns-static-aaaa */
            list agw-dns-static-srv {
                tailf:alt-name "srv-record";
                key "entry-index"; 
                max-elements 1000; 	     
                tailf:info "DNS Static Cache 'SRV' Record database table.";
                leaf entry-index {
                    tailf:info "The index which uniquely identifies this record";
                    type uint16 {
                        range "1..65535";
                    }
                    mandatory true;
                }
                leaf node-name {
                    tailf:info "The full name for the DNS node (_service._proto.domain).";
                    type string {
                        length "1..254";
                    }
                    mandatory true;
                }
                leaf target-name {
                    tailf:info "Domain name of this target host.";
                    type string {
                        length "1..254";
                    }
                    mandatory true;
                }
                leaf port {
                    tailf:info "Port on this target host.";
                    type uint16;
                    mandatory true;
                }
                leaf  priority-field {
                    tailf:info "Priority of this target host";
                    type uint16;
                    tailf:alt-name "priority";
                    default 0;
                }
                leaf weight {
                    tailf:info "Weight of this entry. Default 0";
                    type uint16;
                    default 0;
                }
            } /* agw-dns-static-srv */
            list agw-dns-static-naptr {
                tailf:alt-name "naptr-record";
                key "entry-index"; 
                max-elements 1000; 	     
                tailf:info "DNS Static Cache 'NAPTR' Record database table.";
                leaf entry-index {
                    tailf:info "The index which uniquely identifies this record";
                    type uint16 {
                        range "1..65535";
                    }
                    mandatory true;
                }
                leaf domain-name {
                    tailf:info "The domain for which this record belongs.";
                    type string {
                        length "1..254";
                    }
                    mandatory true;
                }
                leaf services {
                    tailf:info "The service parameters for which this record applies.";
                    type string {
                        length "1..254";
                    }
                    mandatory true;
                }
                leaf replacement {
                    tailf:info "The replacement for this record.";
                    type string {
                        length "1..254";
                    }
                    mandatory true;
                }
                leaf order {
                    tailf:info "The order in which this record will be processed. Default 1";
                    type uint16;
                    default 1;
                }
                leaf preference {
                    tailf:info "The preference for this record. Default 1";
                    type uint16;
                    default 1;
                }
                leaf flags {
                    tailf:info "The control flags for this record.";
                    type enumeration {
                        enum "''";
                        enum "'s'";
                        enum "'S'";
                        enum "'a'";
                        enum "'A'";
                    }
                    mandatory true;
                }
            } /* agw-dns-static-naptr */
        } /* static-cache */
        container agw-dns-if {
            tailf:alt-name "dns-if";
            presence ""; 	     
            tailf:info "DNS Interface config database table.";
            uses routing-instance-name;
            leaf ip-address {
                tailf:info "Source IP address that DNS will use for external messages.";
                type inet:ip-address;
                mandatory true;
            }
            uses dscp;
            leaf override-ttl {
                type string {
                    pattern 'off|(([1-9]([0-9]{1,3})?)|[1-5][0-9]{4}|6([0-4][0-9]{3}|5([0-4][0-9]{2}|5([0-2][0-9]|3[0-5]))))' {
                        tailf:info "Valid values are: off, 1..65535";
                    }  
                }
                tailf:info "Value to override the default cached entry TTL Default off";
                default "off";
            }
            leaf negative-cache-ttl {
                tailf:info "Value to override the default negative cache entry TTL Default 300";
                type uint16 {
                    range "30..5000";
                }
                default 300;
            }
            leaf dynamic-cache-size {
                tailf:info "Size of the dynamic cache (in megabytes) Default 5";
                type uint16 {
                    range "1..10";
                }
                default 5;
            }
            leaf initial-retry-timer {
                tailf:info "Initial query timeout value (in milliseconds) Default 500";
                type uint16 {
                    range "500..2000";
                }
                default 500;
            }
            leaf max-retry-timer {
                tailf:info "Maximum query timeout value (in seconds) Default 10";
                type uint16 {
                    range "1..10";
                }
                default 10;
            }
            leaf retry-count {
                tailf:info "Number of query retries Default 6";
                type uint16 {
                    range "1..10";
                }
                default 6;
            }
        } /* agw-dns-if */
    } /* dns */
} /* mme-sgsn */
} /*submodule*/
