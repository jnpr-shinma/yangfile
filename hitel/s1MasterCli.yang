//////////////////////////////////////////////////////////////////////////
/// @file s1MasterCli.yang
/// @brief Yang definitions for operational commands.
///        "show mme-sgsn interface s1 enb"
///        "show fgw interface s1 enb"
///        "show mme-sgsn interface s102 enb-iws-map"
///        "show mme-sgsn service-area tracking-area"
///        "show fgw service-area tracking-area"
///        "show mme-sgsn service-area tai-enodeb-map"
///        "show fgw service-area tai-enodeb-map"
///
/// Maintained by: HCTA
/// History:
///
/// yyyymmmdd Changed by      Change Reason
/// --------- --------------- --------------------------------------------
/// 2014Jan15 Akshay Wani     AGW-21104 - Initial development
/// 2014Feb28 Adam Floyd      AGW-21104 - Updated callpoint info
/// 2014Mar28 Mike Lesko      AGW-21104 - changed overload-start-sent to string
/// 2014Mar03 Akshay Wani     AGW-21104 - Change enb-iws-map yang model to 
///                                       store operational data in CDB.
/// 2014Apr17 Adam Floyd      AGW-21104 - Add sort-flag to cp opaque data
/// 2014May15 Anuja Chaudhari AGW-21596 - Added support for relocate command
/// 2014Aug15 Adam Floyd      AGW-23534 - Remove fake-key kludge
/// 2014Sep15 Lakshmi Priya   AGW-22082 - Schema upgrade
/// 2014Sep24 Irina Pershwitz AGW-23781 - Tracking-area conflict
///
/// Copyright (c) 2014 HCTA. All Rights Reserved.
///
/// CONFIDENTIALITY AND LIMITED USE
///
/// This software, including any software of third parties embodied herein,
/// contains information and concepts which are confidential to HCTA
/// and such third parties. This software is licensed for use
/// solely in accordance with the terms and conditions of the applicable
/// license agreement with HCTA or its authorized distributor.
//////////////////////////////////////////////////////////////////////////
submodule s1MasterCli{
   belongs-to hcta-epc {
      prefix epc;
   }

   import tailf-common {
      prefix tailf;
   }

   include mmeSgsnConfig;
   include fgwConfig;
   include cmdCommonHcta;
   include s1MasterConfig;
   include upmConfig;

   import ietf-inet-types {
      prefix inet;
   }

   augment "/mme-sgsn/interface/s1" {
      container enb {
      tailf:info "ENodeB";
      tailf:action relocate {
        tailf:info "Operator initiated relocation of an eNodeB ";
        tailf:actionpoint cli-request-command;
        input {
          leaf enodeb-id {
            type uint32;
            tailf:info "ENodeB Identifier.";
            mandatory true;
          }
          leaf plmn-id {
            type string; 
            tailf:info "PLMN Identifier.";
            mandatory true;
          }
          leaf enodeb-type {
            type string;
            tailf:info "ENodeB Identifier Type.";
            mandatory true;
          }
          leaf service {
            type string;
            tailf:info "ENodeB service.";
            mandatory true;
          }
        }
        output {
            uses request-cmd-output;
          }
        }
      }

      list enb-oper {
         /* If these are made keys,
            then leaves will need to move and application adjusted. */
         tailf:info "ENodeB";
         tailf:alt-name "enb";
         config false;
         ordered-by user; // not for use with keyed lists

         tailf:cli-no-key-completion;
         //key "enodeb-name plmn-id enodeb-id enodeb-type ip-address1 ip-address2";

         tailf:callpoint cli_oper_show
         {
            // Callpoint Opaque Data Format (255 chars max):
            // 'min-keys:command path:keyName/keyType keyName/keyType ...:sort-flag(0|1)';
            tailf:opaque '0:mme-sgsn interface s1 enb::1';
         }

         leaf plmn-id {
            type string;
            tailf:display-groups "none detail";
            tailf:info "PLMN Identifier.";
         }
         leaf enodeb-id {
            type uint32;
            tailf:display-groups "none detail";
            tailf:info "ENodeB Identifier.";
         }
         leaf enodeb-type {
            type string;
            tailf:display-groups "none detail";
            tailf:info "ENodeB Identifier Type.";
         }
         leaf ip-address1 {
            type inet:ip-address;
            tailf:display-groups "none detail";
            tailf:info "IP address1.";
         }
         leaf ip-address2 {
            type inet:ip-address;
            tailf:display-groups "none detail";
            tailf:info "IP address2.";
         }
         leaf enodeb-name {
            type string;
            tailf:display-groups "none detail";      
            tailf:info "ENodeB name.";
         }
         leaf process-pid {
            type uint32;
            tailf:display-groups "detail";
            tailf:info "agwMmeS1Enb process PID.";
         }
         leaf service {
            type string;
            tailf:display-groups "none detail";
            tailf:info "agwMmeS1Enb service.";
         }
         leaf overload-start-sent {
            type string;
            tailf:display-groups "detail";
            tailf:info "Indicates if MME overload start message is sent to eNodeB or not.";
         }
         leaf connection-state {
            type string;
            tailf:display-groups "detail";
            tailf:info "The state of this MME's connection to the eNodeB.";
         }
         leaf csg-list {
            type string;
            tailf:display-groups "detail";
            tailf:info "CSG list from eNodeB.";
         }
         leaf cell-access-mode {
            type string;
            tailf:display-groups "detail";
            tailf:info "Home eNodeB type.";
         }
      } /*enb */
   } /* mme-sgsn/interface/s1*/

   augment "/fgw/interface/s1" {
      list enb {
         /* If these are made keys,
            then leaves will need to move and application adjusted. */
         tailf:info "ENodeB";
         config false;
         ordered-by user; // not for use with keyed lists

         tailf:cli-no-key-completion;
         //key "enodeb-name plmn-id enodeb-id enodeb-type ip-address1 ip-address2";

         tailf:callpoint cli_oper_show
         {
            // Callpoint Opaque Data Format (255 chars max):
            // 'min-keys:command path:keyName/keyType keyName/keyType ...:sort-flag(0|1)';
            tailf:opaque '0:fgw interface s1 enb::1';
         }

         leaf plmn-id {
            type string;
            tailf:display-groups "none detail";
            tailf:info "PLMN ID.";
         }
         leaf enodeb-id {
            type uint32;
            tailf:display-groups "none detail";
            tailf:info "ENodeB ID.";
         }
         leaf enodeb-type {
            type string;
            tailf:display-groups "none detail";
            tailf:info "ENodeB Identifier Type.";
         }
         leaf ip-address1 {
            type inet:ip-address;
            tailf:display-groups "none detail";
            tailf:info "IP address1.";
         }
         leaf ip-address2 {
            type inet:ip-address;
            tailf:display-groups "none detail";
            tailf:info "IP address2.";
         }
         leaf enodeb-name {
            type string;
            tailf:display-groups "none detail";
            tailf:info "ENodeB name.";
         }
         leaf process-pid {
            type uint32;
            tailf:display-groups "detail";
            tailf:info "agwMmeS1Enb process PID.";
         }
         leaf process-location {
            type string;
            tailf:display-groups "detail";
            tailf:info "agwMmeS1Enb process location.";
         }
         leaf etrace-app-name {
            type string;
            tailf:display-groups "detail";
            tailf:info "agwMmeS1Enb application name for eTrace.";
         }
         leaf overload-start-sent {
            type boolean;
            tailf:display-groups "detail";
            tailf:info "Indicates if MME overload start message is sent to eNodeB or not.";
         }
         leaf connection-state {
            type string;
            tailf:display-groups "detail";
            tailf:info "The state of this MME's connection to the eNodeB.";
         }
         leaf csg-list {
            type string;
            tailf:display-groups "detail";
            tailf:info "CSG list from eNodeB.";
         }
         leaf cell-access-mode {
            type string;
            tailf:display-groups "detail";
            tailf:info "Home eNodeB type.";
         }
      }
   }

   augment "/mme-sgsn/service-area" {
      list tracking-area-oper {
         tailf:info "Tracking Area";
         tailf:alt-name "tracking-area";
         config false;
         ordered-by user; // not for use with keyed lists

         tailf:cli-no-key-completion;
         //key "plmn-id tac";

         tailf:callpoint cli_oper_show
         {
            // Callpoint Opaque Data Format (255 chars max):
            // 'min-keys:command path:keyName/keyType keyName/keyType ...:sort-flag(0|1)';
            tailf:opaque '0:mme-sgsn service-area tracking-area::1';
         }

         leaf plmn-id { 
            type string;
            tailf:display-groups "none detail";            
            tailf:info "PLMN Identifier.";
         }
         leaf tac {
            type string;
            tailf:display-groups "none detail";
            tailf:info "TAC Identifier.";
         }
         leaf neighbortai-percent-sgwreloc {
            type string;
            tailf:display-groups "detail";
            tailf:info "Neighboring Tracking Area List.";
         }
      }
 
      list tai-enodeb-map {
         tailf:info "TAI eNodeB map";
         config false;
         ordered-by user; // not for use with keyed lists

         tailf:cli-no-key-completion;
         /* If these are made keys,
            then leaves will need to move and application adjusted. */
         //key "enodeb-plmn-id enodeb-id enodeb-type tai-plmn-id tac";

         tailf:callpoint cli_oper_show
         {
            // Callpoint Opaque Data Format (255 chars max):
            // 'min-keys:command path:keyName/keyType keyName/keyType ...:sort-flag(0|1)';
            tailf:opaque '0:mme-sgsn service-area tai-enodeb-map::1';
         }

         leaf enodeb-plmn-id {
            type string;
            tailf:display-groups "none detail";
            tailf:info "ENodeB PLMN Identifier.";
         }
         leaf enodeb-id {
            type uint32;
            tailf:display-groups "none detail";
            tailf:info "ENodeB Identifier.";
         }
         leaf enodeb-type {
            type string;
            tailf:display-groups "none detail";
            tailf:info "ENodeB ID Type.";
         }
         leaf enodeb-name {
            type string;
            tailf:display-groups "none detail";
            tailf:info "ENodeB name.";
         }
         leaf tai-plmn-id {
            type string;
            tailf:display-groups "none detail";
            tailf:info "TAI PLMN Identifier.";
         }
         leaf tac {
            type string;
            tailf:display-groups "none detail";
            tailf:info "TAC Identifier.";
         }
      }
   }
   augment "/fgw/service-area" {
      list tracking-area {
         tailf:info "Tracking Area";
         config false;
         ordered-by user; // not for use with keyed lists

         tailf:cli-no-key-completion;
         //key "plmn-id tac";

         tailf:callpoint cli_oper_show
         {
            // Callpoint Opaque Data Format (255 chars max):
            // 'min-keys:command path:keyName/keyType keyName/keyType ...:sort-flag(0|1)';
            tailf:opaque '0:fgw service-area tracking-area::1';
         }

         leaf plmn-id {
            type string;
            tailf:display-groups "none detail";
            tailf:info "PLMN Identifier.";
         }
         leaf tac {
            type string;
            tailf:display-groups "none detail";
            tailf:info "TAC Identifier.";
         }
         leaf neighbortai-percent-sgwreloc {
            type string;
            tailf:display-groups "detail";
            tailf:info "Neighboring Tracking Area List.";
         }
      }
      list tai-enodeb-map {
         tailf:info "TAI eNodeB map";
         config false;
         ordered-by user; // not for use with keyed lists

         tailf:cli-no-key-completion;
         /* If these are made keys,
            then leaves will need to move and application adjusted. */
         //key "enodeb-plmn-id enodeb-id enodeb-type tai-plmn-id tac";

         tailf:callpoint cli_oper_show
         {
            // Callpoint Opaque Data Format (255 chars max):
            // 'min-keys:command path:keyName/keyType keyName/keyType ...:sort-flag(0|1)';
            tailf:opaque '0:fgw service-area tai-enodeb-map::1';
         }

         leaf enodeb-plmn-id {
            type string;
            tailf:display-groups "none detail";
            tailf:info "ENodeb PLMN Identifier.";
         }
         leaf enodeb-id {
            type uint32;
            tailf:display-groups "none detail";
            tailf:info "ENodeB Identifier.";
         }
         leaf enodeb-type {
            type string;
            tailf:display-groups "none detail";
            tailf:info "ENodeB ID Type.";
         }
         leaf enodeb-name {
            type string;
            tailf:display-groups "none detail";
            tailf:info "ENodeB name.";
         }
         leaf tai-plmn-id {
            type string;
            tailf:display-groups "none detail";
            tailf:info "TAI PLMN Identifier.";
         }
         leaf tac {
            type string;
            tailf:display-groups "none detail";
            tailf:info "TAC Identifier.";
         }
      }
   }

   augment "/mme-sgsn/interface/s102" {
      list enb-iws-map {
         tailf:info "ENodeB IWS Map";
         config false;
         tailf:cdb-oper
         {
            tailf:persistent true;
         }
         key "plmn-id enodeb-id enodeb-type iws-id";

         leaf plmn-id {
            type string;
            tailf:display-groups "none detail";
            tailf:info "PLMN ID.";
         }
         leaf enodeb-id {
            type uint32;
            tailf:display-groups "none detail";
            tailf:info "ENodeB ID.";
         }
         leaf enodeb-type {
            type string;
            tailf:display-groups "none detail";
            tailf:info "ENodeB Type.";
         }
         leaf iws-id {
            type string;
            tailf:display-groups "none detail";
            tailf:info "IWS ID in hex format.";
         }
         leaf iws-ip-address {
            type inet:ip-address;
            tailf:display-groups "none detail";
            tailf:info "IWS IP Address.";
         }
      }
   }
} /*submodule*/
