//////////////////////////////////////////////////////////////////////////
/// @file fgwS1MmeCli.yang
/// @brief Yang groups definitions for fgwS1Mme commands.
///        "show fgw interface s1-mme-association"
///
/// Maintained by: HCTA
/// History:
///
/// yyyymmmdd Changed by      Change Reason
/// --------- --------------- --------------------------------------------
/// 2014Jan15 Akshay Wani     AGW-21104 - Initial development
/// 2014Feb28 Adam Floyd      AGW-21104 - Updated callpoint info
/// 2014Apr17 Adam Floyd      AGW-21104 - Add sort-flag to cp opaque data
/// 2014Aug15 Adam Floyd      AGW-23534 - Remove fake-key kludge
/// 2014Sep15 Lakshmi Priya   AGW-22082 - Schema upgrade.
///
/// Copyright (c) 2014 HCTA. All Rights Reserved.
///
/// CONFIDENTIALITY AND LIMITED USE
///
/// This software, including any software of third parties embodied herein,
/// contains information and concepts which are confidential to HCTA
/// and such third parties. This software is licensed for use
/// solely in accordance with the terms and conditions of the applicable
/// license agreement with HCTA or its authorized distributor.
//////////////////////////////////////////////////////////////////////////
submodule fgwS1MmeCli {
   belongs-to hcta-epc {
      prefix epc;   
   }

   include fgwConfig;
   include fgwS1MmeConfig;
   include cmdCommonHcta;

   import tailf-common {
      prefix tailf;
   }


   augment "/fgw/interface/s1" {
      list s1-mme-association-oper {
         tailf:alt-name s1-mme-association;
         tailf:info "S1-MME peer association";
         config false;
         ordered-by user; // not for use with keyed lists

         tailf:cli-no-key-completion;
         //key mme-name;

         tailf:callpoint cli_oper_show
         {
            // Callpoint Opaque Data Format (255 chars max):
            // 'min-keys:command path:keyName/keyType keyName/keyType ...:sort-flag(0|1)';
            tailf:opaque '0:fgw interface s1 s1-mme-association::1';
         }

         leaf mme-name {
            type string;
            tailf:display-groups "none detail";
            tailf:info "MME peer name";
         }
         leaf location {
            type string;
            tailf:display-groups "none detail";
            tailf:info "Location of fgwS1Mme SU";
         }
         leaf process-pid {
            type uint32;
            tailf:display-groups "none detail";
            tailf:info "fgwS1Mme process PID";
         }
         leaf overload-state {
            type string;
            tailf:display-groups "none detail";
            tailf:info "Overload state";
         }
         leaf relative-capacity {
            type uint32;
            tailf:display-groups "none detail";
            tailf:info "Relative capacity of this MME";
         }
         leaf gummei-plmn-list {
            type string;
            tailf:display-groups "none detail";
            tailf:info "PLMN list received in S1 Setup Response";
         }
         leaf gummei-group-id-list {
            type string;
            tailf:display-groups "none detail";
            tailf:info "Group ID list recevied in S1 Setup Response";
         }
         leaf gummei-mme-code-list {
            type string;
            tailf:display-groups "none detail";
            tailf:info "MME Code List received in S1 Setup Response";
         }
         leaf status-str {
            tailf:alt-name "status";
            type string;
            tailf:display-groups "none detail";
            tailf:info "Status of the connection";
         }
      }
   }
}
