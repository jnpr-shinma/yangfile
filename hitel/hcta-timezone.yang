//////////////////////////////////////////////////////////////////////////
/// @file hcta-timezone.yang
/// @brief Yang definitions timezone config.
/// ----------------------------ATTENTION---------------------------------
/// ----------------------------ATTENTION---------------------------------
/// ----------------------------ATTENTION---------------------------------
/// If there is any change to the timezone-string enum below, please make 
/// corresponding change to /src/cmn/utils/timeZone/date_time_zonespec.csv. 
///
/// Maintained by: HCTA
/// History:
///
/// yyyymmmdd Changed by      Change Reason
/// --------- --------------- --------------------------------------------
/// 2014Jan15 Irina Pershwitz AGW-21103 - Initial development
/// 2014Jun10 Liwen Wang      AGW-21991 - Add more strings from Linux and IANA definition
/// 2014Sep15 Lakshmi Priya   AGW-22082 - Schema upgrade.
/// 2014May21 Nimesh D        AGW-22459 - Error while loading config with
///                           timezone
/// 2014Aug20 Nimesh D        AGW-23536 - Timezone container fix.
///
/// Copyright (c) 2014 HCTA. All Rights Reserved.
///
/// CONFIDENTIALITY AND LIMITED USE
///
/// This software, including any software of third parties embodied herein,
/// contains information and concepts which are confidential to HCTA
/// and such third parties. This software is licensed for use
/// solely in accordance with the terms and conditions of the applicable
/// license agreement with HCTA or its authorized distributor.
//////////////////////////////////////////////////////////////////////////

module hcta-timezone {
  namespace "http://hitachi-cta.com/ns/timezone";
  prefix timezone;

  import tailf-common {
    prefix tailf;
  }

  organization "Hitachi-CTA";
  description
       "The module time-zone.";

  revision 2014-09-18 {
    description  "EPC8.0";
  }

  typedef timezone-string {
       description
         "Time zone name or POSIX-compliant time zone string.";
       type enumeration {
         enum "Africa/Abidjan";
         enum "Africa/Accra";
         enum "Africa/Addis_Ababa";
         enum "Africa/Algiers";
         enum "Africa/Asmera";
         enum "Africa/Bamako";
         enum "Africa/Bangui";
         enum "Africa/Banjul";
         enum "Africa/Bissau";
         enum "Africa/Blantyre";
         enum "Africa/Brazzaville";
         enum "Africa/Bujumbura";
         enum "Africa/Cairo";
         enum "Africa/Casablanca";
         enum "Africa/Ceuta";
         enum "Africa/Conakry";
         enum "Africa/Dakar";
         enum "Africa/Dar_es_Salaam";
         enum "Africa/Djibouti";
         enum "Africa/Douala";
         enum "Africa/El_Aaiun";
         enum "Africa/Freetown";
         enum "Africa/Gaborone";
         enum "Africa/Harare";
         enum "Africa/Johannesburg";
         enum "Africa/Juba";
         enum "Africa/Kampala";
         enum "Africa/Khartoum";
         enum "Africa/Kigali";
         enum "Africa/Kinshasa";
         enum "Africa/Lagos";
         enum "Africa/Libreville";
         enum "Africa/Lome";
         enum "Africa/Luanda";
         enum "Africa/Lubumbashi";
         enum "Africa/Lusaka";
         enum "Africa/Malabo";
         enum "Africa/Maputo";
         enum "Africa/Maseru";
         enum "Africa/Mbabane";
         enum "Africa/Mogadishu";
         enum "Africa/Monrovia";
         enum "Africa/Nairobi";
         enum "Africa/Ndjamena";
         enum "Africa/Niamey";
         enum "Africa/Nouakchott";
         enum "Africa/Ouagadougou";
         enum "Africa/Porto-Novo";
         enum "Africa/Sao_Tome";
         enum "Africa/Timbuktu";
         enum "Africa/Tripoli";
         enum "Africa/Tunis";
         enum "Africa/Windhoek";
         enum "America/Adak";
         enum "America/Anchorage";
         enum "America/Anguilla";
         enum "America/Antigua";
         enum "America/Araguaina";
         enum "America/Argentina/Buenos_Aires";
         enum "America/Argentina/Catamarca";
         enum "America/Argentina/ComodRivadavia";
         enum "America/Argentina/Cordoba";
         enum "America/Argentina/Jujuy";
         enum "America/Argentina/La_Rioja";
         enum "America/Argentina/Mendoza";
         enum "America/Argentina/Rio_Gallegos";
         enum "America/Argentina/Salta";
         enum "America/Argentina/San_Juan";
         enum "America/Argentina/San_Luis";
         enum "America/Argentina/Tucuman";
         enum "America/Argentina/Ushuaia";
         enum "America/Aruba";
         enum "America/Asuncion";
         enum "America/Atikokan";
         enum "America/Atka";
         enum "America/Bahia";
         enum "America/Bahia_Banderas";
         enum "America/Barbados";
         enum "America/Belem";
         enum "America/Belize";
         enum "America/Blanc-Sablon";
         enum "America/Boa_Vista";
         enum "America/Bogota";
         enum "America/Boise";
         enum "America/Cambridge_Bay";
         enum "America/Campo_Grande";
         enum "America/Cancun";
         enum "America/Caracas";
         enum "America/Cayenne";
         enum "America/Cayman";
         enum "America/Chicago";
         enum "America/Chihuahua";
         enum "America/Costa_Rica";
         enum "America/Creston";
         enum "America/Cuiaba";
         enum "America/Curacao";
         enum "America/Danmarkshavn";
         enum "America/Dawson";
         enum "America/Dawson_Creek";
         enum "America/Denver";
         enum "America/Detroit";
         enum "America/Dominica";
         enum "America/Edmonton";
         enum "America/Eirunepe";
         enum "America/El_Salvador";
         enum "America/Ensenada";
         enum "America/Fort_Wayne";
         enum "America/Fortaleza";
         enum "America/Glace_Bay";
         enum "America/Godthab";
         enum "America/Goose_Bay";
         enum "America/Grand_Turk";
         enum "America/Grenada";
         enum "America/Guadeloupe";
         enum "America/Guatemala";
         enum "America/Guayaquil";
         enum "America/Guyana";
         enum "America/Halifax";
         enum "America/Havana";
         enum "America/Hermosillo";
         enum "America/Indiana/Indianapolis";
         enum "America/Indiana/Knox";
         enum "America/Indiana/Marengo";
         enum "America/Indiana/Petersburg";
         enum "America/Indiana/Tell_City";
         enum "America/Indiana/Vevay";
         enum "America/Indiana/Vincennes";
         enum "America/Indiana/Winamac";
         enum "America/Inuvik";
         enum "America/Iqaluit";
         enum "America/Jamaica";
         enum "America/Juneau";
         enum "America/Kentucky/Louisville";
         enum "America/Kentucky/Monticello";
         enum "America/Kralendijk";
         enum "America/La_Paz";
         enum "America/Lima";
         enum "America/Los_Angeles";
         enum "America/Lower_Princes";
         enum "America/Maceio";
         enum "America/Managua";
         enum "America/Manaus";
         enum "America/Marigot";
         enum "America/Martinique";
         enum "America/Matamoros";
         enum "America/Mazatlan";
         enum "America/Menominee";
         enum "America/Merida";
         enum "America/Metlakatla";
         enum "America/Mexico_City";
         enum "America/Miquelon";
         enum "America/Moncton";
         enum "America/Monterrey";
         enum "America/Montevideo";
         enum "America/Montreal";
         enum "America/Montserrat";
         enum "America/Nassau";
         enum "America/New_York";
         enum "America/Nipigon";
         enum "America/Nome";
         enum "America/Noronha";
         enum "America/North_Dakota/Beulah";
         enum "America/North_Dakota/Center";
         enum "America/North_Dakota/New_Salem";
         enum "America/Ojinaga";
         enum "America/Panama";
         enum "America/Pangnirtung";
         enum "America/Paramaribo";
         enum "America/Phoenix";
         enum "America/Port-au-Prince";
         enum "America/Port_of_Spain";
         enum "America/Porto_Acre";
         enum "America/Porto_Velho";
         enum "America/Puerto_Rico";
         enum "America/Rainy_River";
         enum "America/Rankin_Inlet";
         enum "America/Recife";
         enum "America/Regina";
         enum "America/Resolute";
         enum "America/Rio_Branco";
         enum "America/Rosario";
         enum "America/Santa_Isabel";
         enum "America/Santarem";
         enum "America/Santiago";
         enum "America/Santo_Domingo";
         enum "America/Sao_Paulo";
         enum "America/Scoresbysund";
         enum "America/Shiprock";
         enum "America/Sitka";
         enum "America/St_Barthelemy";
         enum "America/St_Johns";
         enum "America/St_Kitts";
         enum "America/St_Lucia";
         enum "America/St_Thomas";
         enum "America/St_Vincent";
         enum "America/Swift_Current";
         enum "America/Tegucigalpa";
         enum "America/Thule";
         enum "America/Thunder_Bay";
         enum "America/Tijuana";
         enum "America/Toronto";
         enum "America/Tortola";
         enum "America/Vancouver";
         enum "America/Virgin";
         enum "America/Whitehorse";
         enum "America/Winnipeg";
         enum "America/Yakutat";
         enum "America/Yellowknife";
         enum "Antarctica/Casey";
         enum "Antarctica/Davis";
         enum "Antarctica/DumontDUrville";
         enum "Antarctica/Macquarie";
         enum "Antarctica/Mawson";
         enum "Antarctica/McMurdo";
         enum "Antarctica/Palmer";
         enum "Antarctica/Rothera";
         enum "Antarctica/South_Pole";
         enum "Antarctica/Syowa";
         enum "Antarctica/Vostok";
         enum "Arctic/Longyearbyen";
         enum "Asia/Aden";
         enum "Asia/Almaty";
         enum "Asia/Amman";
         enum "Asia/Anadyr";
         enum "Asia/Aqtau";
         enum "Asia/Aqtobe";
         enum "Asia/Ashgabat";
         enum "Asia/Ashkhabad";
         enum "Asia/Baghdad";
         enum "Asia/Bahrain";
         enum "Asia/Baku";
         enum "Asia/Bangkok";
         enum "Asia/Beirut";
         enum "Asia/Bishkek";
         enum "Asia/Brunei";
         enum "Asia/Calcutta";
         enum "Asia/Choibalsan";
         enum "Asia/Chongqing";
         enum "Asia/Colombo";
         enum "Asia/Dacca";
         enum "Asia/Damascus";
         enum "Asia/Dhaka";
         enum "Asia/Dili";
         enum "Asia/Dubai";
         enum "Asia/Dushanbe";
         enum "Asia/Gaza";
         enum "Asia/Harbin";
         enum "Asia/Hebron";
         enum "Asia/Ho_Chi_Minh";
         enum "Asia/Hong_Kong";
         enum "Asia/Hovd";
         enum "Asia/Irkutsk";
         enum "Asia/Istanbul";
         enum "Asia/Jakarta";
         enum "Asia/Jayapura";
         enum "Asia/Jerusalem";
         enum "Asia/Kabul";
         enum "Asia/Kamchatka";
         enum "Asia/Karachi";
         enum "Asia/Kashgar";
         enum "Asia/Kathmandu";
         enum "Asia/Khandyga";
         enum "Asia/Kolkata";
         enum "Asia/Krasnoyarsk";
         enum "Asia/Kuala_Lumpur";
         enum "Asia/Kuching";
         enum "Asia/Kuwait";
         enum "Asia/Macau";
         enum "Asia/Magadan";
         enum "Asia/Makassar";
         enum "Asia/Manila";
         enum "Asia/Muscat";
         enum "Asia/Nicosia";
         enum "Asia/Novokuznetsk";
         enum "Asia/Novosibirsk";
         enum "Asia/Omsk";
         enum "Asia/Oral";
         enum "Asia/Phnom_Penh";
         enum "Asia/Pontianak";
         enum "Asia/Pyongyang";
         enum "Asia/Qatar";
         enum "Asia/Qyzylorda";
         enum "Asia/Rangoon";
         enum "Asia/Riyadh";
         enum "Asia/Saigon";
         enum "Asia/Sakhalin";
         enum "Asia/Samarkand";
         enum "Asia/Seoul";
         enum "Asia/Shanghai";
         enum "Asia/Singapore";
         enum "Asia/Taipei";
         enum "Asia/Tashkent";
         enum "Asia/Tbilisi";
         enum "Asia/Tehran";
         enum "Asia/Tel_Aviv";
         enum "Asia/Thimbu";
         enum "Asia/Thimphu";
         enum "Asia/Tokyo";
         enum "Asia/Ujung_Pandang";
         enum "Asia/Ulaanbaatar";
         enum "Asia/Urumqi";
         enum "Asia/Ust-Nera";
         enum "Asia/Vientiane";
         enum "Asia/Vladivostok";
         enum "Asia/Yakutsk";
         enum "Asia/Yekaterinburg";
         enum "Asia/Yerevan";
         enum "Atlantic/Azores";
         enum "Atlantic/Bermuda";
         enum "Atlantic/Canary";
         enum "Atlantic/Cape_Verde";
         enum "Atlantic/Faroe";
         enum "Atlantic/Jan_Mayen";
         enum "Atlantic/Madeira";
         enum "Atlantic/Reykjavik";
         enum "Atlantic/South_Georgia";
         enum "Atlantic/St_Helena";
         enum "Atlantic/Stanley";
         enum "Australia/Adelaide";
         enum "Australia/Brisbane";
         enum "Australia/Broken_Hill";
         enum "Australia/Canberra";
         enum "Australia/Darwin";
         enum "Australia/Eucla";
         enum "Australia/Hobart";
         enum "Australia/Lindeman";
         enum "Australia/Lord_Howe";
         enum "Australia/Melbourne";
         enum "Australia/Perth";
         enum "Australia/Queensland";
         enum "Australia/Sydney";
         enum "Australia/Tasmania";
         enum "Australia/Victoria";
         enum "Australia/Yancowinna";
         enum "Etc/GMT";
         enum "Etc/GMT+0";
         enum "Etc/GMT+1";
         enum "Etc/GMT+10";
         enum "Etc/GMT+11";
         enum "Etc/GMT+12";
         enum "Etc/GMT+2";
         enum "Etc/GMT+3";
         enum "Etc/GMT+4";
         enum "Etc/GMT+5";
         enum "Etc/GMT+6";
         enum "Etc/GMT+7";
         enum "Etc/GMT+8";
         enum "Etc/GMT+9";
         enum "Etc/GMT-0";
         enum "Etc/GMT-1";
         enum "Etc/GMT-10";
         enum "Etc/GMT-11";
         enum "Etc/GMT-12";
         enum "Etc/GMT-13";
         enum "Etc/GMT-14";
         enum "Etc/GMT-2";
         enum "Etc/GMT-3";
         enum "Etc/GMT-4";
         enum "Etc/GMT-5";
         enum "Etc/GMT-6";
         enum "Etc/GMT-7";
         enum "Etc/GMT-8";
         enum "Etc/GMT-9";
         enum "Etc/GMT0";
         enum "Etc/Greenwich";
         enum "Etc/UCT";
         enum "Etc/UTC";
         enum "Etc/Universal";
         enum "Etc/Zulu";
         enum "Europe/Amsterdam";
         enum "Europe/Andorra";
         enum "Europe/Athens";
         enum "Europe/Belfast";
         enum "Europe/Belgrade";
         enum "Europe/Berlin";
         enum "Europe/Bratislava";
         enum "Europe/Brussels";
         enum "Europe/Bucharest";
         enum "Europe/Budapest";
         enum "Europe/Busingen";
         enum "Europe/Chisinau";
         enum "Europe/Copenhagen";
         enum "Europe/Dublin";
         enum "Europe/Gibraltar";
         enum "Europe/Guernsey";
         enum "Europe/Helsinki";
         enum "Europe/Isle_of_Man";
         enum "Europe/Istanbul";
         enum "Europe/Jersey";
         enum "Europe/Kaliningrad";
         enum "Europe/Kiev";
         enum "Europe/Lisbon";
         enum "Europe/Ljubljana";
         enum "Europe/London";
         enum "Europe/Luxembourg";
         enum "Europe/Madrid";
         enum "Europe/Malta";
         enum "Europe/Mariehamn";
         enum "Europe/Minsk";
         enum "Europe/Monaco";
         enum "Europe/Moscow";
         enum "Europe/Nicosia";
         enum "Europe/Oslo";
         enum "Europe/Paris";
         enum "Europe/Podgorica";
         enum "Europe/Prague";
         enum "Europe/Riga";
         enum "Europe/Rome";
         enum "Europe/Samara";
         enum "Europe/San_Marino";
         enum "Europe/Sarajevo";
         enum "Europe/Simferopol";
         enum "Europe/Skopje";
         enum "Europe/Sofia";
         enum "Europe/Stockholm";
         enum "Europe/Tallinn";
         enum "Europe/Tirane";
         enum "Europe/Tiraspol";
         enum "Europe/Uzhgorod";
         enum "Europe/Vaduz";
         enum "Europe/Vatican";
         enum "Europe/Vienna";
         enum "Europe/Vilnius";
         enum "Europe/Volgograd";
         enum "Europe/Warsaw";
         enum "Europe/Zagreb";
         enum "Europe/Zaporozhye";
         enum "Europe/Zurich";
         enum "Indian/Antananarivo";
         enum "Indian/Chagos";
         enum "Indian/Christmas";
         enum "Indian/Cocos";
         enum "Indian/Comoro";
         enum "Indian/Kerguelen";
         enum "Indian/Mahe";
         enum "Indian/Maldives";
         enum "Indian/Mauritius";
         enum "Indian/Mayotte";
         enum "Indian/Reunion";
         enum "Pacific/Apia";
         enum "Pacific/Auckland";
         enum "Pacific/Chatham";
         enum "Pacific/Chuuk";
         enum "Pacific/Easter";
         enum "Pacific/Efate";
         enum "Pacific/Enderbury";
         enum "Pacific/Fakaofo";
         enum "Pacific/Fiji";
         enum "Pacific/Funafuti";
         enum "Pacific/Galapagos";
         enum "Pacific/Gambier";
         enum "Pacific/Guadalcanal";
         enum "Pacific/Guam";
         enum "Pacific/Honolulu";
         enum "Pacific/Johnston";
         enum "Pacific/Kiritimati";
         enum "Pacific/Kosrae";
         enum "Pacific/Kwajalein";
         enum "Pacific/Majuro";
         enum "Pacific/Marquesas";
         enum "Pacific/Midway";
         enum "Pacific/Nauru";
         enum "Pacific/Niue";
         enum "Pacific/Norfolk";
         enum "Pacific/Noumea";
         enum "Pacific/Pago_Pago";
         enum "Pacific/Palau";
         enum "Pacific/Pitcairn";
         enum "Pacific/Pohnpei";
         enum "Pacific/Ponape";
         enum "Pacific/Port_Moresby";
         enum "Pacific/Rarotonga";
         enum "Pacific/Saipan";
         enum "Pacific/Samoa";
         enum "Pacific/Tahiti";
         enum "Pacific/Tarawa";
         enum "Pacific/Tongatapu";
         enum "Pacific/Truk";
         enum "Pacific/Wake";
         enum "Pacific/Wallis";
         enum "Pacific/Yap";
         enum "SystemV/AST4";
         enum "SystemV/AST4ADT";
         enum "SystemV/CST6";
         enum "SystemV/CST6CDT";
         enum "SystemV/EST5";
         enum "SystemV/EST5EDT";
         enum "SystemV/HST10";
         enum "SystemV/MST7";
         enum "SystemV/MST7MDT";
         enum "SystemV/PST8";
         enum "SystemV/PST8PDT";
         enum "SystemV/YST9";
         enum "SystemV/YST9YDT";
         enum "US/Alaska";
         enum "US/Aleutian";
         enum "US/Arizona";
         enum "US/Central";
         enum "US/East-Indiana";
         enum "US/Eastern";
         enum "US/Hawaii";
         enum "US/Indiana-Starke";
         enum "US/Michigan";
         enum "US/Mountain";
         enum "US/Pacific";
         enum "US/Pacific-New";
         enum "US/Samoa";
         enum "UTC";
     }
  }

  leaf timezone {
    tailf:info "Time zone name or POSIX-compliant time zone string.";
    type timezone-string;
  } 

}
