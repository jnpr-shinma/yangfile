/*
//////////////////////////////////////////////////////////////////////////////
/// @file upmConfig.yang
/// @brief This file contains configuration related to UPM.
///
/// History:
///
/// yyyymmmdd Changed by      Change Reason
/// --------- --------------- -------------------------------------------------
/// 2014Sep05 Terri Hennessy  AGW-22104 GTP procedure timers. 
/// 2014Sep05 Gauri C         AGW-22104 Added gn-tunnel-profile
/// 20140918  Lakshmi Priya   AGW-22082 Schema upgrade
/// 2014Sep24 Terri Hennessy  AGW-22104 Remove IP check for gtp-profile
/// 2014Oct21 Akash Gupta     AGW-22104 Enforce default gtp-profile
///
/// Copyright (c) 2014 Hitachi Limited. All Rights Reserved.
///
/// CONFIDENTIALITY AND LIMITED USE
///
/// This software, including any software of third parties embodied herein,
/// contains information and concepts which are confidential to Hitachi
/// and such third parties. This software is licensed for use
/// solely in accordance with the terms and conditions of the applicable
/// license agreement with Hitachi or its authorized distributor.
///
//////////////////////////////////////////////////////////////////////////////
*/

/* upmConfig.yang generated from upmConfig.xml */
submodule upmConfig{

belongs-to hcta-epc {
    prefix epc;
}

import tailf-common {
    prefix tailf;
}

include mmeSgsnConfig;

include fgwConfig;

include cmdCommonHcta;
import ietf-inet-types {
    prefix inet;
}

augment "/mme-sgsn/interface" {
   container gtp {
     /*TODO FIXME_APP_SPRINT6 tailf:validate gtpValidate; */
      presence "";   
      tailf:info "GPRS Tunneling Protocol layer";      
      leaf max-pending-transactions {
         tailf:info "Max pending transactions. Default 20000";
         type uint16 {
            range "100..20000";
         }
         default 20000;
      }
      leaf gtpv1-version {
         tailf:info "Standard version of interface. Default 10.8.0";
         type enumeration {
            enum "9.5.0" {tailf:code-name gtp-gtpv1-version-9-5-0;}
            enum "10.8.0" {tailf:code-name gtp-gtpv1-version-10-8-0;}
         }
         default "10.8.0";
         
      }                               
      leaf gtpv2-version {
         tailf:info "Standard version of interface. Default 10.10.0";
         type enumeration {
            enum "9.5.0" {tailf:code-name gtp-gtpv2-version-9-5-0;}
            enum "10.10.0"{tailf:code-name gtp-gtpv2-version-10-10-0;}
         }
         must "((current() != '9.5.0') or (count(../../../feature/mme-feature-control[name = 'srvcc' and status-field = 'on']) = 0))" {
            error-message
               "If 'mme-sgsn feature control srvcc status' is 'on' then 'gtpv2-version' must be '10.10.0' or above";
         }
         default "10.10.0";
      }  
      list mme-gtp-profile {
         tailf:alt-name "profile";
         tailf:validate gtpProfileValidate {
               tailf:call-once "true";
         }
         key "name";
         max-elements 32;
         /* When SIG VM is configured, default gtp-profile must exist */
         must "((count(../../../system/sig/unit) = 0) or (count(../mme-gtp-profile[name = 'default']) != 0))" { 
            error-message "If 'mme-sgsn system sig' object exists then 'default' must exist";
         }
         tailf:info "GTP profile.";
         leaf name {
            /* Other ddl-specific info for this field. */
            tailf:info "A unique GTP profile name.";
            must "(current() != 'none')" {
                error-message "A profile cannot have a name of 'none'";
            }
            type string {
                length "1..32";
                pattern '((default)|(s101)|[a-zA-Z0-9]([_-]|[A-Za-z0-9])+)' {
                    tailf:info "Valid values are: default, s101, <new-gtp-profile>";
                }
            }

            mandatory true;
         }    
         leaf routing-instance {
            /* Foreign Key */
            tailf:info "Routing Instance associated with 'ip-address'[need to reset all VM to effect a change in value]";

            must "((count(../../mme-gtp-profile[name = 's101']) = 0) or (count(../../mme-gtp-profile[name = 's101']/routing-instance) != 0))" {
error-message "'gtp-profile' should have a valid 'routing-instance' configured before linking to 's101'";
            }
            must "((count(../../mme-gtp-profile[name = 'default']) = 0) or (count(../../mme-gtp-profile[name = 'default']/routing-instance) != 0))" {
error-message "The 'gtp-profile' named 'default' should have a valid 'routing-instance' configured";
            }

            type string
            { 
               length 1..64;
            }  
         } 
         leaf ip-address-v4 {
            tailf:info "Local IPV4 address [need to reset all VM to effect a change in value]";

            must "((count(../../mme-gtp-profile[name = 's101' and ip-address-v4 = '0.0.0.0']) = 0) and ((count(../../mme-gtp-profile[name = 's101']) = 0) or (count(../../mme-gtp-profile[name = 's101']/ip-address-v4) != 0))) " {
error-message "'gtp-profile' should have a valid 'ip-address-v4' configured before linking to 's101'";
            }
            must "((count(../../mme-gtp-profile[name = 'default' and ip-address-v4 != '0.0.0.0']) != 0) and (count(../../mme-gtp-profile[name = 'default']/ip-address-v4) != 0)) " {
error-message "'gtp-profile' should have a valid 'ip-address-v4' configured before linking to 'default'";
            }

            type inet:ipv4-address;
         }
         leaf ip-address-v6 {
            tailf:info "Local IPV6 Address [need to reset all VM to effect a change in value]";
            type inet:ipv6-address;
         }
         uses dscp;
         leaf echo-interval {
            type string {
                  pattern 'disabled|[1-9]|[1-9][0-9]|[1-2][0-9][0-9]|300' {
                     tailf:info "Valid values are: disabled, 1..300";
                  }  
            }
            tailf:info "Echo interval. Default 4";
            default "4";
         }
         leaf t3-echo-response {
            tailf:info "Echo response timer. Default 15";
            type uint8 {
                  range "1..30";
            }
            default 15;
         }
         leaf n3-echo-request {
            tailf:info "Number of echo requests. Default 8";
            type uint8 {
                  range "1..20";
            }
            default 8;
         }
         leaf t3-response {
            tailf:info "Response timer. Default 5";
            type uint8 {
                  range "1..15";
            }
            default 5;
         }
         leaf n3-request {
            tailf:info "Number of requests. Default 2";
            type uint8 {
                  range "1..5";
            }
            default 2;
         }
         leaf t3-response-session-creation {
            tailf:info "Response timer for session creation procedure messages. Default 5; Units seconds";
            type uint8 {
                  range "1..15";
            }
            default 5;
         }
         leaf n3-request-session-creation {
            tailf:info "Number of requests for session creation procedure messages. Default 2";
            type uint8 {
                  range "1..5";
            }
            default 2;
         }
         leaf t3-response-bearer-modification {
            tailf:info "Response timer for bearer modification procedure messages. Default 5; Units seconds";
            type uint8 {
                  range "1..15";
            }
            default 5;
         }
         leaf n3-request-bearer-modification {
            tailf:info "Number of requests for bearer modification procedure messages. Default 2";
            type uint8 {
                  range "1..5";
            }     
            default 2; 
         } 
         leaf t3-response-context-request { 
            tailf:info "Response timer for context request procedure messages. Default 5; Units seconds"; 
            type uint8 {
                  range "1..15";
            }
            default 5;
         }
         leaf n3-request-context-request {
            tailf:info "Number of requests for context request procedure messages. Default 2";
            type uint8 { 
                  range "1..5"; 
            } 
            default 2; }
         leaf t3-response-forward-relocation {
            tailf:info "Response timer for forward relocation procedure messages. Default 5; Units seconds";
            type uint8 {
                  range "1..15";
            }
            default 5;
         }
         leaf n3-request-forward-relocation {
            tailf:info "Number of requests for forward relocation procedure messages. Default 2";
            type uint8 {
                  range "1..5";
            }
            default 2;
         }
         leaf inactivity-timer {
            type string {
                  pattern 'disabled|[1-9]|[1-9][0-9]|[1-2][0-9][0-9]|300' {
                     tailf:info "Valid values are: disabled, 1..300";
                  }  
            }
            tailf:info "Inactivity timer. Default 10";
            default "10";
         }                               
      } /* mme-gtp-profile */
   } /* gtp*/
   
container gn {
    tailf:info "Gn interface to GGSN";
    container mme-gn-if {
        tailf:alt-name "gn-if";
        presence "";	  
        tailf:info "Gn interface";
        leaf gn-tunnel-profile {
            /* Foreign Key */
            /* Note, order of these "must" checks is important.  If both hit,
               then it seems error from second one is issued. */
            must "(count(../../../gtp/mme-gtp-profile[name = current() and ip-address-v4 != '0.0.0.0']) != 0) " {
                error-message "'gtp-profile' should have a valid 'ip-address-v4' configured before linking to 'gn-if'";
            }
            must "(count(../../../gtp/mme-gtp-profile[name = current() and routing-instance]) != 0)" {
                error-message "'gtp-profile' should have a valid 'routing-instance' configured before linking to 'gn-if'";
            }
            must "(count(../../../gtp/mme-gtp-profile[name = current()]) != 0)" {
                error-message "There is no 'mme-sgsn interface gtp profile' object with this 'gtp-profile'";
            }
            tailf:info "GTP profile name associated with the Gn Tunnel interface. [Need to reset the node to effect a change in value for connectivity-related fields (IP, routing-instance, dscp-mark)].";
            type string {
                length "1..32";
            }
            mandatory true;
        }
        leaf pdp-downselect-version {
            tailf:info "Downselected PDP Type value sent to non-supporting dual address bearer. Default ipv4";
            type enumeration {
                enum "ipv4" {tailf:code-name mme-gn-if-pdp-downselect-version-ipv4;}
                enum "ipv6" {tailf:code-name mme-gn-if-pdp-downselect-version-ipv6;}
                enum "ue-selected" {tailf:code-name mme-gn-if-pdp-downselect-version-ue-selected;}
            }
            default "ipv4";
        }
    } /* mme-gn-if */
} /* gn*/
container s11 {
    tailf:info "S11 interface to S-GW";
    container mme-s11-if {
        tailf:alt-name "s11-if";
        presence "";	  
        tailf:info "S11 interface.";
        leaf change-reporting {
            tailf:info "MME provides ULI for mobility events. Default off";
            type enumeration {
                enum "on"  { tailf:code-name s11-if-on;}
                enum "off" { tailf:code-name s11-if-off;}
            }
            default "off";
        }
        leaf uli-inclusion {
            tailf:info "Provide to include user location information in GTPv2 messages. Default standard";
            type enumeration {
                enum "standard" { tailf:code-name s11-if-uli-inclusion-standard;}
                enum "force-in-mbr" { tailf:code-name s11-if-uli-inclusion-force-in-mbr;}
                enum "force-in-all" { tailf:code-name s11-if-uli-inclusion-force-in-all;}
            }
            default "standard";
        }
        leaf ue-timezone-inclusion {
            tailf:info "Include ue-timezone in GTPv2 messages. Default standard";
            type enumeration {
                enum "standard" {tailf:code-name s11-if-ue-timezone-inclusion-standard;}
                enum "force-in-all" {tailf:code-name s11-if-ue-timezone-inclusion-force-in-all;}
            }
            default "standard";
        }
        leaf load-status-private-extension {
            tailf:info "Enable inter-nodal congestion control. Default off";
            type enumeration {
                enum "on"  { tailf:code-name s11-if-on;}
                enum "off" { tailf:code-name s11-if-off;}
            }
            default "off";
        }
        leaf pgw-load-status-lifetime {
            tailf:info "The time to retain current load status for a PGW before reseting it. Default 15";
            type uint8 {
                range "1..30";
            }
            default 15;
        }
        leaf quarantine-non-responsive-pgw {
            tailf:info "Enable Inter-Node congestion control. Default off";
            type enumeration {
                enum "on"  { tailf:code-name s11-if-on;}
                enum "off" { tailf:code-name s11-if-off;}
            }
            default "off";
        }
        leaf pgw-quarantine-duration {
            tailf:info "The time for which a non-responding PGW is removed from PGW selection. Default 15";
            type uint16 {
                range "15..1800";
            }
            default 15;
        }
        leaf gtp-profile {
            /* Note, order of these "must" checks is important.  If both hit,
               then it seems error from second one is issued. */
            must "(count(../../../gtp/mme-gtp-profile[name = current() and ip-address-v4 != '0.0.0.0']) != 0) " {
                error-message "'gtp-profile' should have a valid 'ip-address-v4' configured before linking to 's11-if'";
            }
            must "(count(../../../gtp/mme-gtp-profile[name = current() and routing-instance]) != 0)" {
                error-message "'gtp-profile' should have a valid 'routing-instance' configured before linking to 's11-if'";
            }
            must "(count(../../../gtp/mme-gtp-profile[name = current()]) != 0)" {
                error-message "There is no 'mme-sgsn interface gtp profile' object with this 'gtp-profile'";
            }
            tailf:info "GTP profile name associated with S11 interface. [Need to reset all VM to effect a change in value for connectivity-related fields (IP, routing-instance, dscp-mark)]";
            type string {
                length "1..32";
            }
            mandatory true;
        }
        leaf echoless-path-management {
            tailf:info "Enable echo-less path management. Default disabled";
            type enumeration {
                enum "enabled"  { tailf:code-name s11-if-on;}
                enum "disabled" { tailf:code-name s11-if-off;}
            }
            default "disabled";
        }
    } /* mme-s11-if */
} /* s11*/
container mme-s4 {
    tailf:alt-name "s4";
    tailf:info "S4 interface to S-GW";
    container mme-s4-if {
        tailf:alt-name "s4-if";
        presence "";
        tailf:info "S4 interface";
        leaf gtp-profile {
            /* Note, order of these "must" checks is important.  If both hit,
               then it seems error from second one is issued. */
            must "(count(../../../gtp/mme-gtp-profile[name = current() and ip-address-v4 != '0.0.0.0']) != 0) " {
                error-message "'gtp-profile' should have a valid 'ip-address-v4' configured before linking to 's4-if'";
            }
            must "(count(../../../gtp/mme-gtp-profile[name = current() and routing-instance]) != 0) " {
                error-message "'gtp-profile' should have a valid 'routing-instance' configured before linking to 's4-if'";
            }
            must "(count(../../../gtp/mme-gtp-profile[name = current()]) != 0) " {
                error-message "There is no 'mme-sgsn interface gtp profile' object with this 'gtp-profile'";
            }
            tailf:info "GTP profile name associated with S4 interface. [Need to reset all the VMs to effect a change in value for connectivity-related fields (IP, routing-instance, dscp-mark)]";
            type string {
                length "1..32";
            }
            mandatory true;
        }
        leaf uli-inclusion {
            tailf:info "Provide to include user location information in GTPv2 messages. Default standard";
            type enumeration {
                enum "standard" { tailf:code-name s4-if-uli-inclusion-standard;}
                enum "force-in-all" { tailf:code-name s4-if-uli-inclusion-force-in-all;}
            }
            default "standard";
        }
        leaf ue-timezone-inclusion {
            tailf:info "Include ue-timezone in GTPv2 messages. Default standard";
            type enumeration {
                enum "standard" {tailf:code-name s4-if-ue-timezone-inclusion-standard;}
                enum "force-in-all" {tailf:code-name s4-if-ue-timezone-inclusion-force-in-all;}
            }
            default "standard";
        }
    } /* mme-s4-if */
} /* s4*/
container s102 {
    tailf:info "S102 interface to CDMA IWS";
    container mme-s102-if {
        tailf:alt-name "s102-if";
        presence "";	  
        tailf:info "S102 interface.";
        must "count(../../../feature/mme-feature-control[name = 's102' and status-field = 'on']) != 0" {
            error-message
            "If 's102-if' object exists then 'mme-sgsn feature control s102 status' must be 'on'";
        }
        uses routing-instance-name; 
        leaf hss-realm-for-min-query {
            must "((../version != '10.0.0') or (../hss-realm-for-min-query = 'none'))" {
                error-message
                "If 'mme-sgsn interface s102 s102-if version' is '10.0.0' then 'hss-realm-for-min-query' must be 'none'";
            }
            must "((../version != 'icd-v2') or (../hss-realm-for-min-query != 'none'))" {
                error-message
                "If 'mme-sgsn interface s102 s102-if version' is 'icd-v2' then 'hss-realm-for-min-query' must not be 'none'";
            }
            must "((../version != 'icd-v2') or (count(../../../diameter/mme-realm-peer-map[realm-name = current()]) != 0) or (../hss-realm-for-min-query = 'none'))" {
                error-message
                "There is no 'mme-sgsn interface diameter realm-peer-map' object with this 'realm-name'";
            }
            tailf:info "Realm for MIN to IMSI translation.";
            type string {
                length "3..127";
            }
            mandatory true;
        }
        leaf ip-address-v4 {
            tailf:info "IP address.";
            type inet:ipv4-address;
            mandatory true;
        }
        leaf ip-address-v6 {
            tailf:info "IP V6 address. Default 0:0:0:0:0:0:0:0";
            type inet:ipv6-address;
            default "0:0:0:0:0:0:0:0";
        }
        leaf port {
            tailf:info "Local port number. Default 23272";
            type uint16 {
                range "1..65535";
            }
            default 23272;
        }
        leaf version {
            tailf:info "3GPP spec applicable to this interface is TS29.277. Default 10.0.0";
            type enumeration {
                enum "icd-v2" {tailf:code-name mme-s102-if-version-icd-v2;}
                enum "10.0.0" {tailf:code-name mme-s102-if-version-10-0-0;}
            }
            default "10.0.0";
        }
        uses dscp;
        leaf echo-interval {
            type string {
                pattern 'disable|[1-9]|[1-9][0-9]|[1-2][0-9][0-9]|300' {
                    tailf:info "Valid values are: disable, 1..300";
                }  
            }
            tailf:info "Echo interval. Default 4";
            default "4";
        }
        leaf t-ack-21-timer {
            tailf:info "Response timer. Default 5";
            type uint8 {
                range "1..15";
            }
            default 5;
        }
        leaf request-retry {
            tailf:info "Number of request retries. Default 1";
            type uint8 {
                range "0..5";
            }
            default 1;
        }
        leaf max-pending-transactions {
            tailf:info "Max pending transactions. Default 250";
            type uint16 {
                range "100..10000";
            }
            default 250;
        }
        leaf priority-paging {
            must "((../priority-paging != 'enable') or (../version = 'icd-v2'))" {
                error-message
                "If 'priority-paging' is 'enable' then 'version' must be 'icd-v2'";
            }
            tailf:info "Enable use of GEC bit to build priority paging IE. Default disable";
            type enumeration {
                enum "enable" {tailf:code-name mme-s102-if-priority-paging-enable;}
                enum "disable" {tailf:code-name mme-s102-if-priority-paging-disable;}
            }
            default "disable";
        }
        leaf enb-map-lifetime {
            tailf:info "Time to retain an eNB to IWS mapping without being refreshed. Default 24";
            type uint8 {
                range "1..48";
            }
            default 24;
        }
    } /* mme-s102-if */
    list mme-iws {
        tailf:alt-name "iws";
        key "iws-id"; 
        max-elements 200;
        unique "ip-address port";
        must "count(../mme-s102-if) != 0" {
            error-message
            "'s102 iws' entry cannot be added as 'mme-sgsn interface s102 s102-if' entity does not exist";
        }
        tailf:info "Interworking System to support 1XRTT CSFB.";
        leaf iws-id {
            type string {
                pattern '0x[a-f0-9]{2,4}' {
                    tailf:info "Valid values are: hexadecimal values of length 4..6 including a leading '0x'";
                }  
            }
            tailf:info "The identifier of the IWS in hex format.";
            mandatory true;
        }
        leaf ip-address {
            tailf:info "IP address of the IWS.";
            type inet:ip-address;
            mandatory true;
        }
        leaf port {
            tailf:info "Remote port number. Default 23272";
            type uint16 {
                range "1..65535";
            }
            default 23272;
        }
    } /* mme-iws */
} /* s102 */
} /* interface */
augment "/mme-sgsn/engineering" {
    container mme-upm-engineering {
        tailf:alt-name "upm-engineering";
        presence "";
        tailf:info "UPM Engineering.";
        leaf recovery-window-time {
            tailf:info "UPM load balancing recovery window timer. Default 180";
            type uint32 {
                range "0..65535";
            }
            default 180;
        }
        leaf mobility-path-weight {
            tailf:info "UPM load balancing based on path weight of mobility. Default 20";
            type uint16 {
                range "0..1600";
            }
            default 20;
        }
        leaf tunnel-path-weight {
            tailf:info "UPM load balancing based on path weight of tunnel. Default 1000";
            type uint16 {
               range "0..1600";  
            }
            default 1000;
        }
        leaf s101-path-weight {
            tailf:info "UPM load balancing based on path weight of s101 in seconds. Default 3";
            type uint16 {
               range "0..1600";
            }
            default 3;
        }
        leaf s102-path-weight {
            tailf:info "UPM load balancing based on path weight of s102. Default 25";
            type uint16 {
               range "0..1600";
            }
            default 25;
        }
        leaf fxa-path-weight {
            tailf:info "UPM load balancing based on path weight of fxa. Default 2";
            type uint16 {
               range "0..1600";
            }
            default 2;
        }
    }

    container mme-upm-tps-congestion {
        tailf:alt-name "upm-tps-congestion";
        presence "";  
        tailf:info "UPM TPS congestion control.";
        leaf minor-onset {
            tailf:info "Tps congestion minor alarm set. Default 4000";
            type uint32 {
                range "0..100000";
            }
            default 4000;
        }
        leaf minor-abate {
            tailf:info "Tps congestion minor alarm clear. Default 3500";
            type uint32 {
                range "0..100000";
            }
            default 3500;
        }
        leaf minor-ovld {
            tailf:info "When enabled minor threshold levels in use. Default enable";
            type enumeration {
                enum "enable" {tailf:code-name mme-upm-tps-congestion-minor-ovld-enable;}
                enum "disable" {tailf:code-name mme-upm-tps-congestion-minor-ovld-disable;}
            }
            default "enable";
        }
        leaf major-onset {
            tailf:info "Tps congestion major alarm set. Default 4500";
            type uint32 {
                range "0..100000";
            }
            default 4500;
        }
        leaf major-abate {
            tailf:info "Tps congestion major alarm clear. Default 4100";
            type uint32 {
                range "0..100000";
            }
            default 4100;
        }
        leaf major-ovld {
            tailf:info "When enabled major threshold level in use. Default enable";
            type enumeration {
                enum "enable" {tailf:code-name mme-upm-tps-congestion-major-ovld-enable;}
                enum "disable" {tailf:code-name mme-upm-tps-congestion-major-ovld-disable;}
            }
            default "enable";
        }
        leaf critical-onset {
            tailf:info "Tps congestion critical alarm set. Default 5000";
            type uint32 {
                range "0..100000";
            }
            default 5000;
        }
        leaf critical-abate {
            tailf:info "Tps congestion critical alarm clear. Default 4600";
            type uint32 {
                range "0..100000";
            }
            default 4600;
        }
        leaf critical-ovld {
            tailf:info "When enabled critical threshold level in use. Default enable";
            type enumeration {
                enum "enable" {tailf:code-name mme-upm-tps-congestion-critical-ovld-enable;}
                enum "disable" {tailf:code-name mme-upm-tps-congestion-critical-ovld-disable;}
            }
            default "enable";
        }
    } /* mme-upm-tps-congestion */
} /* engineering */
} /*submodule*/
