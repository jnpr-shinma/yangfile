//////////////////////////////////////////////////////////////////////////
/// @file mmeStatisticsConfig.yang
/// @brief Yang definitions statistics config.
///
/// Maintained by: HCTA
/// History:
///
/// yyyymmmdd Changed by      Change Reason
/// --------- --------------- --------------------------------------------
/// 2014Jan15 Irina Pershwitz AGW-21103 - Initial development
/// 2014Feb05 Irina Pershwitz AGW-21103 - remove alt-name
/// 2014Mar27 Nimesh D        AGW-21104 - Removed "presence" tag
/// 2014Apr17 Adam Floyd      AGW-21104 - Block global show-all
/// 2014Sep15 Lakshmi priya   AGW-22082 - Schema upgrade
/// 2014Sep09 Sumit Madaan    AGW-23232 - Prop Activity
/// 2014Sep04 Ajit Singh      AGW-22912 - Prop Activity.
///
/// Copyright (c) 2014 HCTA. All Rights Reserved.
///
/// CONFIDENTIALITY AND LIMITED USE
///
/// This software, including any software of third parties embodied herein,
/// contains information and concepts which are confidential to HCTA
/// and such third parties. This software is licensed for use
/// solely in accordance with the terms and conditions of the applicable
/// license agreement with HCTA or its authorized distributor.
//////////////////////////////////////////////////////////////////////////

submodule mmeStatisticsConfig{

   belongs-to hcta-epc {
       prefix epc; 
   }

   import tailf-common {
      prefix tailf;
   }

   include mmeSgsnConfig;
   include fgwConfig;

   augment "/mme-sgsn" {
      container statistics {
         tailf:info "Statistics objects";
         tailf:cli-incomplete-show-path;
         leaf collection-interval {
            tailf:info "Statistics collection interval. Default 5";
            type enumeration{
               enum 5 {tailf:code-name mme-statistics-collection-interval-5;}
               enum 15 {tailf:code-name mme-statistics-collection-interval-15;}
               enum 30 {tailf:code-name mme-statistics-collection-interval-30;}
            }  
            default 5;
         }
         leaf retention-report {
            tailf:info "Statistics retention-report. Default 288";
            type uint16 {
                 range 2..8928;
            }
            default 288;
         }
         leaf retention-archive {
             tailf:info "Statistics retention-archive. Default 10";
             type uint16 {
                range 1..8928;
             }  
             default 10;
             tailf:hidden true; 
         }

      } /* statistics */
   } /* sgsn-mme */

   augment "/fgw" {
      container statistics {
         tailf:info "Statistics objects";
         tailf:cli-incomplete-show-path;
         leaf collection-interval {
            tailf:info "Statistics collection interval. Default 5";
            type enumeration{
               enum 5 {tailf:code-name fgw-statistics-collection-interval-5;}
               enum 15 {tailf:code-name fgw-statistics-collection-interval-15;}
               enum 30 {tailf:code-name fgw-statistics-collection-interval-30;}
            }  
            default 5;
         }
         leaf retention-report {
            tailf:info "Statistics retention-report. Default 288";
            type uint16 {
                 range 2..8928;
            }
            default 288;
         }
         leaf retention-archive {
             tailf:info "Statistics retention-archive. Default 288";
             type uint16 {
                range 1..8928;
             }     
             default 288;
         }
   
      } /* fgw-statistics */
   } /* fgw */
} /* submodule */
