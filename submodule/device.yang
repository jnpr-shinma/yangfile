submodule device {
    belongs-to "juniper" {
        prefix "juniper";
    }
    organization "juniper";
    revision "2015-01-01" {
        description "Initial revision. ";
    }
    // definitions follow. . .
}
